/******************************************************
* Copyright (C) 2023 isoftstone Technologies Co., Ltd. All rights reserved.
* Module description & tree structure
******************************************************/
module openEuler-hostname {
  namespace "urn:huawei:yang:openEuler-hostname";
  prefix "hostname";

  organization
    "isoftstone";

  contact
    "Huawei Industrial Base
     Bantian, Longgang
     Shenzhen 518129
     People's Republic of China
     Website: http://www.huawei.com
     Email: support@huawei.com";

  description
    "This module contains a collection of YANG definitions for
     hostname config.
     The real path is : /etc/hostname";

  revision 2023-07-14 {
    description "Initial revision.";
    reference "";
  }

  // extension statements
  // feature statements
  // identity statements
  // typedef statements
  // grouping statements
  // data definition statements
  // augment statements
  // rpc statements
  // notification statements

  extension path{
    argument "filePath";
    description "The real path corresponding to the hostname file.";
  }

  extension type{
     argument "type";
     description "The type of this configuration file.";
  }

  extension spacer{
    argument "spacer";
    description "Spacer between configuration item and configuration value.";
  }

  container hostname {

    description "the conf file in hostname modules.";

    container hostname_config {

      description "The file name is hostname";

      hostname:path "openEuler:/etc/hostname";
      hostname:type "hostname";
      hostname:spacer "";
    }
  }
}
