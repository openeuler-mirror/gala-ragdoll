/******************************************************
* Copyright (C) 2023 isoftstone Technologies Co., Ltd. All rights reserved.
* Module description & tree structure
******************************************************/
module openEuler-chrony {
  namespace "urn:huawei:yang:openEuler-chrony";
  prefix "chrony";

  organization
    "huawei";

  contact
    "Huawei Industrial Base
     Bantian, Longgang
     Shenzhen 518129
     People's Republic of China
     Website: http://www.huawei.com
     Email: support@huawei.com";

  description
    "This module contains a collection of YANG definitions for
     chrony config.
     The real path is : /etc/chrony.conf";

  revision 2023-09-18 {
    description "Initial revision.";
    reference "";
  }

  // extension statements
  // feature statements
  // identity statements
  // typedef statements
  // grouping statements
  // data definition statements
  // augment statements
  // rpc statements
  // notification statements

  extension path{
    argument "filePath";
    description "The real path corresponding to the chrony file.";
  }

  extension type{
     argument "type";
     description "The type of this configuration file.";
  }

  extension spacer{
    argument "spacer";
    description "Spacer between configuration item and configuration value.";
  }

  container chrony {

    description "the conf file in chrony modules.";

    container chrony_config {

      description "The file name is chrony";

      chrony:path "openEuler:/etc/chrony.conf";
      chrony:type "text";
      chrony:spacer "";
    }
  }
}
