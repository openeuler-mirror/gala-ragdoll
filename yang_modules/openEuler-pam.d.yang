/******************************************************
* Copyright (C) 2023 isoftstone Technologies Co., Ltd. All rights reserved.
* Module description & tree structure
******************************************************/
module openEuler-pam.d {
  namespace "urn:huawei:yang:openEuler-pam.d";
  prefix "pam";

  organization
    "isoftstone";

  contact
    "Huawei Industrial Base
     Bantian, Longgang
     Shenzhen 518129
     People's Republic of China
     Website: http://www.huawei.com
     Email: support@huawei.com";

  description
    "This module contains a collection of YANG definitions for
     pam.d directory config.
     The real path is : /etc/pam.d";

  revision 2023-09-04 {
    description "Initial revision.";
    reference "";
  }

  // extension statements
  // feature statements
  // identity statements
  // typedef statements
  // grouping statements
  // data definition statements
  // augment statements
  // rpc statements
  // notification statements

  extension path{
    argument "filePath";
    description "The real path corresponding to the pam.d directory file.";
  }

  extension type{
     argument "type";
     description "The type of this configuration file.";
  }

  extension spacer{
    argument "spacer";
    description "Spacer between configuration item and configuration value.";
  }

  container pam {

    description "the conf file in pam.d directory modules.";

    container pam_config {

      description "The file name is pam.d directory file";

      pam:path "openEuler:/etc/pam.d";
      pam:type "pam";
      pam:spacer "";
    }
  }
}
